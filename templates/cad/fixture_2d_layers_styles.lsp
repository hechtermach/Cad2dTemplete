; Fixture 2D CAD initialization script V1.5
; Usage: APPLOAD this file, then run FIXTURE2D_INIT in AutoCAD.

(defun fixture2d-layer (name color ltype / )
  (command "_.-LAYER" "_M" name "_C" color "" "_L" ltype "" "")
)

(defun c:FIXTURE2D_INIT ( / )
  (setvar "INSUNITS" 4)
  (setvar "LTSCALE" 1)
  (setvar "PSLTSCALE" 1)
  (setvar "CELTSCALE" 1)
  (fixture2d-layer "BORDER_FRAME" "7" "Continuous")
  (fixture2d-layer "TITLE_BLOCK" "2" "Continuous")
  (fixture2d-layer "REVISION" "4" "Continuous")
  (fixture2d-layer "VIEW_VISIBLE" "7" "Continuous")
  (fixture2d-layer "VIEW_HIDDEN" "8" "Hidden")
  (fixture2d-layer "VIEW_CENTER" "1" "Center")
  (fixture2d-layer "DIM" "3" "Continuous")
  (fixture2d-layer "TEXT_NOTE" "5" "Continuous")
  (fixture2d-layer "DATUM_GDT" "6" "Continuous")
  (fixture2d-layer "QC_BALLOON" "30" "Continuous")
  (fixture2d-layer "LOGO_HUAWEI" "1" "Continuous")
  (fixture2d-layer "HATCH_SECTION" "9" "Continuous")
  (fixture2d-layer "HOLE_TABLE" "140" "Continuous")
  (fixture2d-layer "KEY_CHARACTERISTIC" "1" "Continuous")
  (fixture2d-layer "INSPECTION_METHOD" "5" "Continuous")
  (fixture2d-layer "SURFACE_TREATMENT" "4" "Continuous")
  (fixture2d-layer "WELD_MACHINING" "30" "Continuous")
  (fixture2d-layer "REFERENCE_3D" "6" "Center")
  (fixture2d-layer "SUPPLIER_ACK" "2" "Continuous")
  (fixture2d-layer "CONSTRUCTION" "8" "Center")
  (fixture2d-layer "NON_PRINT" "253" "Continuous")
  (command "_.STYLE" "STD_CN" "simsun.ttc" "0" "1" "0" "_N" "_N")
  (command "_.STYLE" "STD_EN" "arial.ttf" "0" "1" "0" "_N" "_N")
  (command "_.-DIMSTYLE" "_R" "Standard")
  (setvar "DIMTXSTY" "STD_CN")
  (setvar "DIMTXT" 2.5)
  (setvar "DIMASZ" 2.5)
  (setvar "DIMEXO" 1.0)
  (setvar "DIMEXE" 1.5)
  (setvar "DIMDLI" 7.0)
  (setvar "DIMDEC" 2)
  (setvar "DIMTAD" 1)
  (setvar "DIMCLRD" 3)
  (setvar "DIMCLRE" 3)
  (setvar "DIMCLRT" 3)
  (command "_.-DIMSTYLE" "_S" "FIXTURE2D_MM")
  (princ "\nFixture 2D layers, text styles and dimension style initialized.")
  (princ)
)
